# Mapping_testfile

# Specification: Specification Document

## SR001 (functional_Requirement)
Import ReqIF
- status: Draft
- allocation_to_component: Software
- asil: none
- comment: no comment

### HLR001 (functional_Requirement)
Import SpecObject Type
- status: Draft
- allocation_to_component: Software
- asil: none
- comment: no comment

#### LLR001 (functional_Requirement)
Map requirement_ID to UID
- allocation_to_component: Software
- asil: none
- status: Draft
- comment: no comment

##### LLR001-T001 (functional_Requirement)
Test of requirement_ID mapping
- allocation_to_component: Software
- asil: none
- status: Draft
- target_value: requirement_ID is equal to UID
- comment: Convert SpecObject to Requirement Object, compare IDs

##### LLR001-T002 (functional_Requirement)
Test of malformed requirement_ID mapping
- status: Draft
- allocation_to_component: Software
- asil: none
- target_value: Conversion throws an error
- comment: Convert malformed SpecObject to Requirement Object, compare IDs

##### LL001-T003 (functional_Requirement)
Test of missing requirement_ID mapping
- status: Draft
- allocation_to_component: Software
- asil: none
- target_value: Conversion throws an error
- comment: malformed SpecObject to Requirement Object, compare IDs

#### LLR002 (functional_Requirement)
Map traceability to REFS
- status: Draft
- allocation_to_component: Software
- asil: none
- comment: no comment

##### LLR002-T001 (functional_Requirement)
Test of traceability mapping
- status: Draft
- allocation_to_component: Software
- asil: none
- target_value: traceability is equal to REFS
- comment: Convert SpecObject to Requirement Object, compare references

##### LLR002-T002 (functional_Requirement)
Test of malformed traceability mapping
- status: Draft
- allocation_to_component: Software
- asil: none
- target_value: Conversion throws an error
- comment: Convert malformed SpecObject to Requirement Object, compare references

##### LLR002-T003 (functional_Requirement)
Test of missing traceability mapping
- status: Draft
- allocation_to_component: Software
- asil: none
- target_value: Print a warning
- comment: Convert malformed SpecObject to Requirement Object, compare references

#### LLR003 (functional_Requirement)
Map allocation to SPECIAL FIELD(allocation)
- status: Draft
- allocation_to_component: Software
- asil: none
- comment: no comment

##### LLR003-T001 (functional_Requirement)
Test of allocation mapping
- status: Draft
- allocation_to_component: Software
- asil: none
- target_value: allocation is equal to SPECIAL FIELD(allocation)
- comment: Convert SpecObject to Requirement Object, compare allocation

##### LLR003-T002 (functional_Requirement)
Test of malformed allocation mapping
- status: Draft
- allocation_to_component: Software
- asil: none
- target_value: Conversion throws an error
- comment: Convert malformed SpecObject to Requirement Object, compare allocation

#### LLR004 (functional_Requirement)
Map asil to SPECIAL FIELD(asil)
- status: Draft
- allocation_to_component: Software
- asil: none
- comment: no comment

##### LLR004-T001 (functional_Requirement)
Test of asil mapping
- status: Draft
- allocation_to_component: Software
- asil: none
- target_value: asil is equal to SPECIAL FIELD(asil)
- comment: Convert SpecObject to Requirement Object, compare asil

##### LLR004-T002 (functional_Requirement)
Test of malformed asil mapping
- status: Draft
- allocation_to_component: Software
- asil: none
- target_value: Conversion throws an error
- comment: Convert malformed SpecObject to Requirement Object, compare asil

#### LLR005 (functional_Requirement)
Map status to STATUS
- status: Draft
- allocation_to_component: Software
- asil: none
- comment: no comment

##### LLR005-T001 (functional_Requirement)
Test of status mapping
- status: Draft
- allocation_to_component: Software
- asil: none
- target_value: status is equal to STATUS
- comment: Convert SpecObject to Requirement Object, compare status

##### LLR005-T002 (functional_Requirement)
Test of malformed status mapping
- allocation_to_component: Software
- asil: none
- target_value: Conversion throws an error
- comment: Convert malformed SpecObject to Requirement Object, compare status
- status: Draft

#### LLR006 (functional_Requirement)
Map comment to COMMENT
- allocation_to_component: Software
- asil: none
- comment: no comment
- status: Draft

##### LLR006-T001 (functional_Requirement)
Test of comment mapping
- status: Draft
- allocation_to_component: Software
- asil: none
- target_value: comment is equal to COMMENT
- comment: Convert SpecObject to Requirement Object, compare comment

##### LLR006-T002 (functional_Requirement)
Test of malformed comment mapping
- status: Draft
- allocation_to_component: Software
- asil: none
- target_value: Conversion throws an error
- comment: Convert malformed SpecObject to Requirement Object, compare comment

#### LLR007 (functional_Requirement)
Map functional_description to TITLE
- status: Draft
- allocation_to_component: Software
- asil: none
- comment: no comment

##### LLR007-T001 (functional_Requirement)
Test of functional_description mapping
- status: Draft
- allocation_to_component: Software
- asil: none
- target_value: functional_description is equal to TITLE
- comment: Convert SpecObject to Requirement Object, compare functional_description

##### LLR007-T002 (functional_Requirement)
Test of malformed functional_description mapping
- status: Draft
- allocation_to_component: Software
- asil: none
- target_value: Conversion throws an error
- comment: Convert malformed SpecObject to Requirement Object, compare functional_description

##### LLR007-T003 (functional_Requirement)
Test of missing functional_description mapping
- status: Draft
- allocation_to_component: Software
- asil: none
- target_value: Print a warning
- comment: Convert malformed SpecObject to Requirement Object, compare functional_description

### HLR101 (technical_Requirement)
Import SpecObject Type
- status: Draft
- allocation: Software
- asil: none
- comment: no comment

#### LLR101 (technical_Requirement)
Map requirement_ID to UID
- status: Draft
- allocation: Software
- asil: none
- comment: no comment

##### LLR101-T001 (technical_Requirement)
Test of requirement_ID mapping
- status: Draft
- allocation: Software
- asil: none
- target_value: requirement_ID is equal to UID
- comment: Convert SpecObject to Requirement Object, compare IDs

##### LLR101-T002 (technical_Requirement)
Test of malformed requirement_ID mapping
- status: Draft
- allocation: Software
- asil: none
- target_value: Conversion throws an error
- comment: Convert malformed SpecObject to Requirement Object, compare IDs

##### LLR101-T003 (technical_Requirement)
Test of missing requirement_ID mapping
- status: Draft
- allocation: Software
- asil: none
- target_value: Conversion throws an error
- comment: Convert malformed SpecObject to Requirement Object, compare IDs

#### LLR102 (technical_Requirement)
Map traceability to REFS
- status: Draft
- allocation: Software
- asil: none
- comment: no comment

##### LLR102-T001 (technical_Requirement)
Test of traceability mapping
- status: Draft
- allocation: Software
- asil: none
- target_value: traceability is equal to REFS
- comment: Convert SpecObject to Requirement Object, compare references

##### LLR102-T002 (technical_Requirement)
Test of malformed traceability mapping
- status: Draft
- allocation: Software
- asil: none
- target_value: Conversion throws an error
- comment: Convert malformed SpecObject to Requirement Object, compare references

##### LLR102-T003 (technical_Requirement)
Test of missing traceability mapping
- status: Draft
- allocation: Software
- asil: none
- target_value: Print a warning
- comment: Convert malformed SpecObject to Requirement Object, compare references

#### LLR103 (technical_Requirement)
Map allocation_to_component to SPECIAL FIELD(allocation_to_component)
- status: Draft
- allocation: Software
- asil: none
- comment: no comment

##### LLR103-T001 (technical_Requirement)
Test of allocation_to_component mapping
- status: Draft
- allocation: Software
- asil: none
- target_value: allocation_to_component is equal to SPECIAL FIELD(allocation_to_component)
- comment: Convert SpecObject to Requirement Object, compare allocation_to_component

##### LLR103-T002 (technical_Requirement)
Test of malformed allocation_to_component mapping
- status: Draft
- allocation: Software
- asil: none
- target_value: Conversion throws an error
- comment: Convert malformed SpecObject to Requirement Object, compare allocation_to_component

#### LLR104 (technical_Requirement)
Map asil to SPECIAL FIELD(asil)
- status: Draft
- allocation: Software
- asil: none
- comment: no comment

##### LLR104-T001 (technical_Requirement)
Test of asil mapping
- status: Draft
- allocation: Software
- asil: none
- target_value: asil is equal to SPECIAL FIELD(asil)
- comment: Convert SpecObject to Requirement Object, compare asil

##### LLR104-T002 (technical_Requirement)
Test of malformed asil mapping
- status: Draft
- allocation: Software
- asil: none
- target_value: Conversion throws an error
- comment: Convert malformed SpecObject to Requirement Object, compare asil

#### LLR105 (technical_Requirement)
Map status to STATUS
- status: Draft
- allocation: Software
- asil: none
- comment: no comment

##### LLR105-T001 (technical_Requirement)
Test of status mapping
- status: Draft
- allocation: Software
- asil: none
- target_value: status is equal to STATUS
- comment: Convert SpecObject to Requirement Object, compare status

##### LLR105-T002 (technical_Requirement)
Test of malformed status mapping
- status: Draft
- allocation: Software
- asil: none
- target_value: Conversion throws an error
- comment: Convert malformed SpecObject to Requirement Object, compare status

#### LLR106 (technical_Requirement)
Map comment to COMMENT
- status: Draft
- allocation: Software
- asil: none
- comment: no comment

##### LLR106-T001 (technical_Requirement)
Test of comment mapping
- status: Draft
- allocation: Software
- asil: none
- target_value: comment is equal to COMMENT
- comment: Convert SpecObject to Requirement Object, compare comment

##### LLR106-T002 (technical_Requirement)
Test of malformed comment mapping
- status: Draft
- allocation: Software
- asil: none
- target_value: Conversion throws an error
- comment: Convert malformed SpecObject to Requirement Object, compare comment

#### LLR107 (technical_Requirement)
Map technical_description to TITLE
- status: Draft
- allocation: Software
- asil: none
- comment: no comment

##### LLR107-T001 (technical_Requirement)
Test of technical_description mapping
- status: Draft
- allocation: Software
- asil: none
- target_value: technical_description is equal to TITLE
- comment: Convert SpecObject to Requirement Object, compare technical_description

##### LLR107-T002 (technical_Requirement)
Test of malformed technical_description mapping
- status: Draft
- allocation: Software
- asil: none
- target_value: Conversion throws an error
- comment: Convert malformed SpecObject to Requirement Object, compare technical_description

##### LLR107-T003 (technical_Requirement)
Test of missing technical_description mapping
- status: Draft
- allocation: Software
- asil: none
- target_value: Print a warning
- comment: Convert malformed SpecObject to Requirement Object, compare technical_description

#### LLR108 (technical_Requirement)
Map target_value to SPECIAL FIELD(target_value)
- status: Draft
- allocation: Software
- asil: none
- comment: no comment

##### LLR108-T001 (technical_Requirement)
Test of target_value mapping
- status: Draft
- allocation: Software
- asil: none
- target_value: target_value is equal to SPECIAL FIELD(target_value)
- comment: Convert SpecObject to Requirement Object, compare target_value

##### LLR108-T002 (technical_Requirement)
Test of malformed target_value mapping
- status: Draft
- allocation: Software
- asil: none
- target_value: Conversion throws an error
- comment: Convert malformed SpecObject to Requirement Object, compare target_value

##### LLR108-T003 (technical_Requirement)
Test of missing target_value mapping
- status: Draft
- allocation: Software
- asil: none
- target_value: Print a warning
- comment: Convert malformed SpecObject to Requirement Object, compare target_value
