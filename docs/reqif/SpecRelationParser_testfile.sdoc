[DOCUMENT]
TITLE: SpecRelationParser Requirements
SPECIAL_FIELDS:
- NAME: ALLOCATION
  TYPE: String
- NAME: ASIL
  TYPE: String
- NAME: TARGET_VALUE
  TYPE: String
- NAME: ALLOCATION_TO_COMPONENT
  TYPE: String
- NAME: TYPE
  TYPE: String
- NAME: INITIAL_CONDITION
  TYPE: String
- NAME: TEST_SEQUENCE
  TYPE: String
- NAME: REFERENCE
  TYPE: String

[FREETEXT]
Defining the Requirements for the SpecRelationParser
[/FREETEXT]

[SECTION]
TITLE: Mapping technical requirements

[REQUIREMENT]
UID: HLR301
STATUS: Draft
SPECIAL_FIELDS:
  ALLOCATION: Software
  ASIL: none
REFS:
- TYPE: Parent
  VALUE: SR001
TITLE: The SpecRelationParser shall parse an Etree Element (SpecRelation) and return the data necessary for parsing of this type of SpecObjectRef.

[REQUIREMENT]
UID: LLR301
STATUS: Draft
SPECIAL_FIELDS:
  ALLOCATION_TO_COMPONENT: Software
  ASIL: none
  TARGET_VALUE: UID
REFS:
- TYPE: Parent
  VALUE: HLR301
TITLE: The SpecRelationParser shall parse an Etree Element (SpecRelation) and return the RelationMap.
COMMENT: >>>
no comment
<<<

[REQUIREMENT]
UID: LLR301-T001
STATUS: Draft
SPECIAL_FIELDS:
  TYPE: Software
  INITIAL_CONDITION: An Etree Element containing a SPEC-RELATIONS xml object
  TEST_SEQUENCE: The Element is parsed by the Parser and returns a Map of Target and Source values. The returned relation map is compared to the known values.
  TARGET_VALUE: known target an source values
REFS:
- TYPE: Parent
  VALUE: LLR301
- TYPE: File
  VALUE: ..\tests\unit\strictdoc\import\reqif
TITLE: Test that parsing a correct SPEC-RELATIONS Object returns the correct map.

[REQUIREMENT]
UID: LLR301-T002
STATUS: Draft
SPECIAL_FIELDS:
  TYPE: Software
  INITIAL_CONDITION: An Etree Element containing a SPEC-RELATION xml object with a malformed ID
  TEST_SEQUENCE: The Element, containing a malformed SpecRelations Map, is parsed by the Parser and returns an Exception. The returned Exception is verified
  TARGET_VALUE: ValueError("specrelations_invalidID")
REFS:
- TYPE: Parent
  VALUE: LLR301
- TYPE: File
  VALUE: ..\..\tests\unit\strictdoc\import\reqif
TITLE: Test that parsing a SPEC-RELATIONS Object with a malformed ID raises a ValueError("spec_relations_invalidID")

[REQUIREMENT]
UID: LLR301-T003
STATUS: Draft
SPECIAL_FIELDS:
  TYPE: Software
  INITIAL_CONDITION: An Etree Element containing a SPEC-RELATIONS xml object, containing a SPEC_RELATION with no Source
  TEST_SEQUENCE: The Element, containing a missing SpecRelations Map, is parsed by the Parser and returns an Exception. The returned Exception is verified
  TARGET_VALUE: ValueError("specrelations_missingID")
REFS:
- TYPE: Parent
  VALUE: LLR301
- TYPE: File
  VALUE: ..\..\..\..\tests\unit\strictdoc\import\reqif\test_specrelation.py
TITLE: Test that parsing a SPEC-RELATIONS Object with a missing ID raises a ValueError("spec_relations_missingID").

[/SECTION]
