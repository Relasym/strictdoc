[DOCUMENT]
TITLE: Requirements for SpecObject mapping of functional Requirements 
SPECIAL_FIELDS:
- NAME: ALLOCATION
  TYPE: String
- NAME: ASIL
  TYPE: String
- NAME: TARGET_VALUE
  TYPE: String
- NAME: ALLOCATION_TO_COMPONENT
  TYPE: String
- NAME: TYPE
  TYPE: String
- NAME: INITIAL_CONDITION
  TYPE: String
- NAME: TEST_SEQUENCE
  TYPE: String

[FREETEXT]
Defining the technical tests for mapping from ReqIf files to SDOC
[/FREETEXT]

[SECTION]
TITLE: Mapping functional requirements

[REQUIREMENT]
UID: HLR001
STATUS: Draft
SPECIAL_FIELDS:
  ALLOCATION: Software
  ASIL: none
REFS:
- TYPE: Parent
  VALUE: HLR010
TITLE: The SpecObjectParser shall map functional requirements.

[REQUIREMENT]
UID: HLR001-T001
SPECIAL_FIELDS:
  TYPE: Software
  INITIAL_CONDITION: The etree element is passed into the SpecObjectParser function.
  TEST_SEQUENCE: The functional requirement shall be passed into the function as an etree element and the function returns a Requirement Object which is compared to a predefined Requirement Object.
  TARGET_VALUE: The predefined Requirement Object.
REFS:
- TYPE: Parent
  VALUE: HLR001
- TYPE: File
  VALUE: ..\..\..\tests\unit\strictdoc\import\reqif
TITLE: The test function shall test the mapping of the etree element to a Requirement Object.

[REQUIREMENT]
UID: LLR001
STATUS: Draft
SPECIAL_FIELDS:
  ALLOCATION_TO_COMPONENT: Software
  ASIL: none
  TARGET_VALUE: UID
REFS:
- TYPE: Parent
  VALUE: HLR001
TITLE: The mapping function shall map requirement_ID to UID.
COMMENT: >>>
no comment
<<<

[REQUIREMENT]
UID: LLR001-T001
SPECIAL_FIELDS:
  TYPE: Software
  INITIAL_CONDITION: ReqIF requirement_ID is passed into the mapping function.
  TEST_SEQUENCE: The correct value for the requirement_ID shall be passed into the function and the function returns the same value as result and compares it to the predefined test value.
  TARGET_VALUE: true
REFS:
- TYPE: Parent
  VALUE: LLR001
- TYPE: File
  VALUE: ..\..\..\tests\unit\strictdoc\import\reqif
TITLE: The test function shall test the mapping of the ReqIF attribute requirement_ID to the SDOC attribute UID.

[REQUIREMENT]
UID: LLR001-T002
STATUS: Draft
SPECIAL_FIELDS:
  TYPE: Software
  INITIAL_CONDITION: ReqIF requirement_ID is passed into the mapping function.
  TEST_SEQUENCE: The malformed requirement_ID shall be passed to the function and the function raises an ecxeption.
  TARGET_VALUE: true
REFS:
- TYPE: Parent
  VALUE: LLR001
- TYPE: File
  VALUE: ..\..\..\tests\unit\strictdoc\import\reqif
TITLE: The test function shall test the mapping of the malformed ReqIF attribute requirement_ID to the SDoC attribute UID.

[REQUIREMENT]
UID: LLR001-T003
STATUS: Draft
SPECIAL_FIELDS:
  TYPE: Software
  INITIAL_CONDITION: ReqIF requirement_ID is passed into the mapping function.
  TEST_SEQUENCE: The empty value for the requirement_ID shall be passed to the function and the function raises an ecxeption.
  TARGET_VALUE: true
REFS:
- TYPE: Parent
  VALUE: LLR001
- TYPE: File
  VALUE: ..\..\..\tests\unit\strictdoc\import\reqif
TITLE: The test function shall test the mapping of the missing ReqIF attribute requirement_ID to the SDoC attribute UID.

[REQUIREMENT]
UID: LLR002
STATUS: Draft
SPECIAL_FIELDS:
  ALLOCATION_TO_COMPONENT: Software
  ASIL: none
  TARGET_VALUE: SPECIAL FIELD(allocation)
REFS:
- TYPE: Parent
  VALUE: HLR001
TITLE: The mapping function shall map allocation to SPECIAL FIELD(allocation).
COMMENT: >>>
no comment
<<<

[REQUIREMENT]
UID: LLR002-T001
STATUS: Draft
SPECIAL_FIELDS:
  TYPE: Software
  INITIAL_CONDITION: ReqIF allocation is passed into the mapping function.
  TEST_SEQUENCE: The correct value for the allocation shall be passed to the function and the function returns the same value as result and compares it to the predefined test value.
  TARGET_VALUE: true
REFS:
- TYPE: Parent
  VALUE: LLR002
- TYPE: File
  VALUE: ..\..\..\tests\unit\strictdoc\import\reqif
TITLE: The test function shall test the mapping of the ReqIF attribute allocation to the SDoC attribute SPECIAL FIELD(allocation).

[REQUIREMENT]
UID: LLR002-T002
STATUS: Draft
SPECIAL_FIELDS:
  TYPE: Software
  INITIAL_CONDITION: ReqIF allocation is passed into the mapping function.
  TEST_SEQUENCE: The malformed allocation shall be passed to the function and the function raises an ecxeption.
  TARGET_VALUE: true
REFS:
- TYPE: Parent
  VALUE: LLR002
- TYPE: File
  VALUE: ..\..\..\tests\unit\strictdoc\import\reqif
TITLE: The test function shall test the mapping of the malformed ReqIF attribute allocation to the SDoC attribute SPECIAL FIELD(allocation).

[REQUIREMENT]
UID: LLR003
STATUS: Draft
SPECIAL_FIELDS:
  ALLOCATION_TO_COMPONENT: Software
  ASIL: none
  TARGET_VALUE: SPECIAL FIELD(asil)
REFS:
- TYPE: Parent
  VALUE: HLR001
TITLE: The mapping function shall map asil to SPECIAL FIELD(asil).
COMMENT: >>>
no comment
<<<

[REQUIREMENT]
UID: LLR003-T001
STATUS: Draft
SPECIAL_FIELDS:
  TYPE: Software
  INITIAL_CONDITION: ReqIF asil is passed into the mapping function.
  TEST_SEQUENCE: The correct value for the asil shall be passed to the function and the function returns the same value as result and compares it to the predefined test value.
  TARGET_VALUE: true
REFS:
- TYPE: Parent
  VALUE: LLR003
- TYPE: File
  VALUE: ..\..\..\tests\unit\strictdoc\import\reqif
TITLE: The test function shall test the mapping of the ReqIF attribute asil to the SDoC attribute SPECIAL FIELD(asil).

[REQUIREMENT]
UID: LLR003-T002
STATUS: Draft
SPECIAL_FIELDS:
  TYPE: Software
  INITIAL_CONDITION: ReqIF asil is passed into the mapping function.
  TEST_SEQUENCE: The malformed asil shall be passed to the function and the function raises an ecxeption.
  TARGET_VALUE: true
REFS:
- TYPE: Parent
  VALUE: LLR003
- TYPE: File
  VALUE: ..\..\..\tests\unit\strictdoc\import\reqif
TITLE: The test function shall test the mapping of the malformed ReqIF attribute asil to the SDoC attribute SPECIAL FIELD(asil).

[REQUIREMENT]
UID: LLR004
STATUS: Draft
SPECIAL_FIELDS:
  ALLOCATION_TO_COMPONENT: Software
  ASIL: none
  TARGET_VALUE: STATUS
REFS:
- TYPE: Parent
  VALUE: HLR001
TITLE: The mapping function shall map status to STATUS.
COMMENT: >>>
no comment
<<<

[REQUIREMENT]
UID: LLR004-T001
STATUS: Draft
SPECIAL_FIELDS:
  TYPE: Software
  INITIAL_CONDITION: ReqIF status is passed into the mapping function.
  TEST_SEQUENCE: The correct value for the status shall be passed to the function and the function returns the same value as result and compares it to the predefined test value.
  TARGET_VALUE: true
REFS:
- TYPE: Parent
  VALUE: LLR004
- TYPE: File
  VALUE: ..\..\..\tests\unit\strictdoc\import\reqif
TITLE: The test function shall test the mapping of the ReqIF attribute status to the SDoC attribute STATUS.

[REQUIREMENT]
UID: LLR004-T002
STATUS: Draft
SPECIAL_FIELDS:
  TYPE: Software
  INITIAL_CONDITION: ReqIF status is passed into the mapping function.
  TEST_SEQUENCE: The malformed status shall be passed to the function and the function raises an ecxeption.
  TARGET_VALUE: true
REFS:
- TYPE: Parent
  VALUE: LLR004
- TYPE: File
  VALUE: ..\..\..\tests\unit\strictdoc\import\reqif
TITLE: The test function shall test the mapping of the malformed ReqIF attribute status to the SDoC attribute STATUS.

[REQUIREMENT]
UID: LLR005
STATUS: Draft
SPECIAL_FIELDS:
  ALLOCATION_TO_COMPONENT: Software
  ASIL: none
  TARGET_VALUE: TITLE
REFS:
- TYPE: Parent
  VALUE: HLR001
TITLE: The mapping function shall map functional_description to TITLE.
COMMENT: >>>
no comment
<<<

[REQUIREMENT]
UID: LLR005-T001
STATUS: Draft
SPECIAL_FIELDS:
  TYPE: Software
  INITIAL_CONDITION: ReqIF functional_description is passed into the mapping function.
  TEST_SEQUENCE: The correct value for the functional_description shall be passed to the function and the function returns the same value as result and compares it to the predefined test value.
  TARGET_VALUE: true
REFS:
- TYPE: Parent
  VALUE: LLR005
- TYPE: File
  VALUE: ..\..\..\tests\unit\strictdoc\import\reqif
TITLE: The test function shall test the mapping of the ReqIF attribute functional_description to the SDoC attribute TITLE.

[REQUIREMENT]
UID: LLR005-T002
STATUS: Draft
SPECIAL_FIELDS:
  TYPE: Software
  INITIAL_CONDITION: ReqIF functional_description is passed into the mapping function.
  TEST_SEQUENCE: The malformed functional_description shall be passed to the function and the function raises an ecxeption.
  TARGET_VALUE: true
REFS:
- TYPE: Parent
  VALUE: LLR005
- TYPE: File
  VALUE: ..\..\..\tests\unit\strictdoc\import\reqif
TITLE: The test function shall test the mapping of the malformed ReqIF attribute functional_description to the SDoC attribute TITLE.

[REQUIREMENT]
UID: LLR005-T003
STATUS: Draft
SPECIAL_FIELDS:
  TYPE: Software
  INITIAL_CONDITION: ReqIF functional_description is passed into the mapping function.
  TEST_SEQUENCE: The empty value for the functional_description shall be passed to the function and the function raises an ecxeption.
  TARGET_VALUE: true
REFS:
- TYPE: Parent
  VALUE: LLR005
- TYPE: File
  VALUE: ..\..\..\tests\unit\strictdoc\import\reqif
TITLE: The test function shall test the mapping of the missing ReqIF attribute functional_description to the SDoC attribute TITLE.

[/SECTION]
