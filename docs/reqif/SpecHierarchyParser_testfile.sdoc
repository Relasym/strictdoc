[DOCUMENT]
TITLE: SpecHierarchyParser Requirements
SPECIAL_FIELDS:
- NAME: ALLOCATION
  TYPE: String
- NAME: ASIL
  TYPE: String
- NAME: TARGET_VALUE
  TYPE: String
- NAME: ALLOCATION_TO_COMPONENT
  TYPE: String
- NAME: TYPE
  TYPE: String
- NAME: INITIAL_CONDITION
  TYPE: String
- NAME: TEST_SEQUENCE
  TYPE: String

[FREETEXT]
Defining the Requirements for the SpecHierarchyParser
[/FREETEXT]

[SECTION]
TITLE: Requirements

[REQUIREMENT]
UID: HLR501
STATUS: Draft
SPECIAL_FIELDS:
  ALLOCATION: Software
  ASIL: none
REFS:
- TYPE: Parent
  VALUE: SR001
TITLE: The SpecHierarchyParser shall parse an Etree Element (SpecHierarchy) and return the data necessary for parsing of this type of SpecObjectRef. Key: Child, Value: Parent

[REQUIREMENT]
UID: LLR501
STATUS: Draft
SPECIAL_FIELDS:
  ALLOCATION_TO_COMPONENT: Software
  ASIL: none
  TARGET_VALUE: UID
REFS:
- TYPE: Parent
  VALUE: HLR501
TITLE: The SpecHierarchyParser shall parse an Etree Element (SpecHierarchy) and return the HierarchyMap.
COMMENT: >>>
no comment
<<<

[REQUIREMENT]
UID: LLR501-T001
STATUS: Draft
SPECIAL_FIELDS:
  TYPE: Software
  INITIAL_CONDITION: An Etree Element containing a SPECIFICATIONS xml object
  TEST_SEQUENCE: The Element is parsed by the Parser and returns a Map of Child and Parent values. The returned HierarchyMap is compared to the known values.
  TARGET_VALUE: known target an source values
REFS:
- TYPE: Parent
  VALUE: LLR501
- TYPE: File
  VALUE: ..\..\tests\unit\strictdoc\import\reqif
TITLE: Test that parsing a correct SPEC-HIERARCHY Object returns the correct map.

[REQUIREMENT]
UID: LLR501-T002
STATUS: Draft
SPECIAL_FIELDS:
  TYPE: Software
  INITIAL_CONDITION: An Etree Element containing a SPECIFICATIONS xml object with a malformed ID
  TEST_SEQUENCE: The Element, containing a malformed Specifications Map, is parsed by the Parser and returns an Exception. The returned Exception is verified
  TARGET_VALUE: ValueError("spechierarchy_invalidID")
REFS:
- TYPE: Parent
  VALUE: LLR501
- TYPE: File
  VALUE: ..\..\tests\unit\strictdoc\import\reqif
TITLE: Test that parsing a SPEC-HIERARCHY Object with a malformed ID raises a ValueError("spechierarchy_invalidID")

[/SECTION]
