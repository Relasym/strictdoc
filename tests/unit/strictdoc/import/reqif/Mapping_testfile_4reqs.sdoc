[DOCUMENT]
TITLE: Testfile for first tests of mapping function
SPECIAL_FIELDS:
- NAME: ALLOCATION
  TYPE: String
- NAME: ASIL
  TYPE: String
- NAME: TARGET_VALUE
  TYPE: String
- NAME: ALLOCATION_TO_COMPONENT
  TYPE: String
- NAME: TYPE
  TYPE: String
- NAME: INITIAL_CONDITION
  TYPE: String
- NAME: TEST_SEQUENCE
  TYPE: String
- NAME: REFERENCE
  TYPE: String

[FREETEXT]
Defining the technical tests for mapping from ReqIf files to SDOC
[/FREETEXT]

[SECTION]
TITLE: Mapping requirements

[REQUIREMENT]
UID: SR001
STATUS: Draft
SPECIAL_FIELDS:
  ALLOCATION: Software
  ASIL: none
TITLE: The import function shall import a .reqif file and convert it to an .sdoc file

[REQUIREMENT]
UID: HLR001
STATUS: Draft
SPECIAL_FIELDS:
  ALLOCATION: Software
  ASIL: none
REFS:
- TYPE: Parent
  VALUE: SR001
TITLE: The import function shall import a SpecObject from the .reqif file.

[REQUIREMENT]
UID: LLR001
STATUS: Draft
SPECIAL_FIELDS:
  ALLOCATION_TO_COMPONENT: Software
  ASIL: none
  TARGET_VALUE: UID
REFS:
- TYPE: Parent
  VALUE: HLR001
TITLE: The mapping function shall map requirement_ID to UID.
COMMENT: >>>
no comment
<<<

[REQUIREMENT]
UID: LLR001-T001
STATUS: Draft
SPECIAL_FIELDS:
  TYPE: Software
  INITIAL_CONDITION: ReqIF requirement_ID is passed into the mapping function.
  TEST_SEQUENCE: The correct value for the requirement_ID shall be passed to the function and the function returns the same value as result and compares it to the predefined test value.
  TARGET_VALUE: true
  REFERENCE: none
REFS:
- TYPE: Parent
  VALUE: LLR001
- TYPE: File
  VALUE: ..\..\..\tests\unit\strictdoc\import\reqif
TITLE: The test function shall test the mapping of the ReqIF attribute requirement_ID to the SDoC attribute UID.
COMMENT: >>>
no comment
<<<

[REQUIREMENT]
UID: LLR001-T002
STATUS: Draft
SPECIAL_FIELDS:
  TYPE: Software
  INITIAL_CONDITION: ReqIF status is passed into the mapping function.
  TEST_SEQUENCE: The correct value for status shall be passed to the function and the function returns the same value as result and compares it to the predefined test value.
  TARGET_VALUE: true
  REFERENCE: tests\unit\strictdoc
REFS:
- TYPE: Parent
  VALUE: LLR001
TITLE: The test function shall test the mapping of the ReqIF attribute status to the SDoC attribute STATUS.
COMMENT: >>>
no comment
<<<

[/SECTION]
